# ---------------------------------------------------------------------------
# Repo: https://github.com/ceremcem/assembly-dimensions
# ---------------------------------------------------------------------------
import FreeCAD
import re 
echo = FreeCAD.Console.PrintMessage
warn = FreeCAD.Console.PrintWarning


def get_plane(p1, p2, p3): 
	edge1 = p1 - p2 
	edge2 = p1 - p3 
	normal = edge1.cross(edge2)
	return (p1, normal)

def get_element_plane(shape):
    v = shape.Vertexes
    return get_plane(v[0].Point, v[1].Point, v[2].Point)

doc_name = App.ActiveDocument.Label

sheets = App.ActiveDocument.findObjects('Spreadsheet::Sheet')

alph = 'ABCDEFGHIJKLMNOPQRSTUVWXYZ'
max_null_cells = 3

def get_shape(obj):
	for f in obj:
		try: 
			if f.Shape:
				return f.Shape 
		except:
			pass

def calc_dist(label1, label2):
	shape1 = get_shape(App.ActiveDocument.getObjectsByLabel(label1))
	shape2 = get_shape(App.ActiveDocument.getObjectsByLabel(label2))
	x1 = shape1.Vertexes[0].Point 
	x2 = get_element_plane(shape2)
	dist = x1.distanceToPlane(*x2)
	return dist 

def calc_dist2(label1, label2):
	#echo("App.ActiveDocument.getObjectsByLabel('%s')[0].Shape" % label1)
	shape1 = get_shape(App.ActiveDocument.getObjectsByLabel(label1))
	shape2 = get_shape(App.ActiveDocument.getObjectsByLabel(label2))
	dist = shape1.Vertexes[0].Point.distanceToPlane(shape2.BoundBox.Center, shape2.Faces[0].Surface.Axis)
	return dist 


cell_regex = re.compile('^([A-Z]+)([0-9]+)$')
def get_cells(sheet): 
	return filter(cell_regex.search, sheet.PropertiesList)

def next_col(cell_name, dist=1):
	match = cell_regex.match(cell_name)
	if match:
		col_name = match.group(1)
		row_num = match.group(2)
		next_col_name = chr(ord(col_name) + dist)
		return "%s%s" % (next_col_name, row_num)
	else:
		raise "how come no match?"
	

cmd_regex = re.compile('^#!\s?([a-z-]+)\s?(.*)')
for sheet in sheets: 
	for cell in get_cells(sheet):
		#echo('cell: %s (next col: %s)\n' % (cell, next_col(cell)))
		content = sheet.get(cell)			
		try:
			search = cmd_regex.search(content)
		except:
			# if not a string 
			continue 

		if search: 
			#echo('command row found: ' + content)
			cmd = search.group(1)
			try: 
				args = search.group(2)
			except: 
				args = '' 
			#echo("command is: %s param is: %s\n" % (cmd, args))

			# Use document name as parameter source 
			if cmd == 'doc-name' and len(args) > 0: 
				regex_pattern = re.compile(args)
				match = regex_pattern.search(doc_name)
				echo('found regex: %s\n' % args)
				if match:
					for g in range(0, len(match.groups())):
						sheet.set(next_col(cell, g+1), match.group(g+1))

			elif cmd == 'distance' or cmd == 'dist':
				_from, label1, _to, label2 = args.split()
				if _from == 'from' and _to == 'to':
					echo('Distance from %s to %s: ' % (label1, label2))
					dest_cell = next_col(cell)
					diff_cell = next_col(dest_cell)
					try:			
						#dist = calc_dist(label1, label2)	
						dist = calc_dist2(label1, label2)

						if dist < 0:
							dist = -dist
						curr = sheet.get(dest_cell)
						sheet.set(dest_cell, '=%f mm' % dist)
						sheet.set(diff_cell, str(curr))
						echo('%f mm (written into %s) (prev: %s)\n' % (dist, dest_cell, str(curr)))	
					except Exception, e:
						sheet.set(dest_cell, '=ERR_ASSEMBLY_DIMENSIONS')
						warn('ERROR while calculating distance in cell %s: %s\n' % (cell, str(e)))


App.ActiveDocument.recompute()
